MY-RX-CHANNEL-MIB DEFINITIONS ::= BEGIN 
IMPORTS 
	enterprises, OBJECT-TYPE, MODULE-IDENTITY
		FROM SNMPv2-SMI
	DisplayString, INTEGER
		FROM SNMPv2-TC;
		
	RxChannelInfo MODULE-IDENTITY ::= { enterprises 1001}
	
	RxFecType OBJECT-TYPE
		SYNTAX INTEGER 
		MAX-ACCESS read-write
		STATUS current
		DESCRIPTION
			"6: Turbo  7:LDPC   (仅支持6和7)    RFT=6(Turbo编码)"
	::= { RxChannelInfo 1 }

    RxDemodulateMode OBJECT-TYPE
		SYNTAX INTEGER 
		MAX-ACCESS read-only
		STATUS current
		DESCRIPTION
			"0:BPSK     1:QPSK     2:OQPSK      3:8PSK      4:16-QAM    5:8-QAM     6:16APSK    
            7:32APSK    8~15:预留  16:无效      RMD=1(QPSK方式) 失锁时返回16"
	::= { RxChannelInfo 2 }

    RxRolloffFactor OBJECT-TYPE
		SYNTAX INTEGER 
		MAX-ACCESS read-write
		STATUS current
		DESCRIPTION
			"0: 0.1     1:0.25      2:0.35      3:0.15      4:0.2"
	::= { RxChannelInfo 3 }

    RxIfFreq OBJECT-TYPE
		SYNTAX DisplayString 
		MAX-ACCESS read-only
		STATUS current
		DESCRIPTION
			"分辨率:100HZ  RFQ=1234.5678(发射频率1234.5678 MHZ)"
	::= { RxChannelInfo 4 }

    RxRfFreq OBJECT-TYPE
		SYNTAX DisplayString 
		MAX-ACCESS read-write
		STATUS current
		DESCRIPTION
			"终端发射频率 分辨率:100HZ 值= LNB LO ± RFQ, 如果BUC LO为零,则返回0  RAF=31251.3456(MHZ)"
	::= { RxChannelInfo 5 }

    RxFecCodeRate OBJECT-TYPE
		SYNTAX INTEGER 
		MAX-ACCESS read-only
		STATUS current
		DESCRIPTION
			"0: 5/16(turbo)     1:21/44(turbo)      2:1/2       3:2/3(仅8-PSK TCM 或 8-QAM)     4:3/4       5:7/8   6:0.95(仅turbo)
            7:1/1(无FEC编码)    8:1/3       9:4/5       10:5/6      11:6/7      12:8/9    255:无效  RCR=5(码率7/8)  失锁时返回255"
	::= { RxChannelInfo 6 }

    RxBW OBJECT-TYPE
		SYNTAX DisplayString 
		MAX-ACCESS read-write
		STATUS current
		DESCRIPTION
			"单位KHZ 分辨率=100HZ   RBW=1500.0(发射带宽1.5MHZ)"
	::= { RxChannelInfo 7 }

    RxErrCodeRate OBJECT-TYPE
		SYNTAX DisplayString 
		MAX-ACCESS read-only
		STATUS current
		DESCRIPTION
			"评估的接收误码率，以科学计数法表示。如果未锁定，则返回99999    BER=2.5E6(误码率2.5*10-6)"
	::= { RxChannelInfo 8 }

    RxEbN0 OBJECT-TYPE
		SYNTAX DisplayString 
		MAX-ACCESS read-only
		STATUS current
		DESCRIPTION
			"Eb/N0值，分辨率：0.1dB，范围：0~16dB   如果未锁定，则返回99.9  如果其值大于16.0dB，则返回EBN=+016  EBN=15.7(Eb/N0=15.7 dB)"
	::= { RxChannelInfo 9 }

    RxSpectrumInvert OBJECT-TYPE
		SYNTAX INTEGER 
		MAX-ACCESS read-write
		STATUS current
		DESCRIPTION
			"0: 正常  1:翻转    RSI=0(发射频谱正常)"
    ::= { RxChannelInfo 10 }


    RxSignalIntension OBJECT-TYPE
		SYNTAX DisplayString 
		MAX-ACCESS read-only
		STATUS current
		DESCRIPTION
			"返回接收信号的强度值，单位 dBm，范围：-5 ~ -99 dBm     格式：ccxx
            cc = 代码(GT:大于；LT:小于；==：等于    xx = 值(取负值))    RSL=LT99(接收信号强度小于 -99dBm    RSL==52(接收信号等于 -52dBm))"
	::= { RxChannelInfo 11 }

    RxSysmbolRate OBJECT-TYPE
		SYNTAX DisplayString 
		MAX-ACCESS read-only
		STATUS current
		DESCRIPTION
			"单位 ksymbols/sec 分辨率 1sps 范围：4.8ksps~15.0Msps   RSR=04123.777(发射符号速率4123.777ksymbols/sec)"
	::= { RxChannelInfo 12 }

    ChannelStatus OBJECT-TYPE
		SYNTAX INTEGER 
		MAX-ACCESS read-write
		STATUS current
		DESCRIPTION
			"0: 关闭(默认)  1:打开    RXO=1(接收通道打开)"
	::= { RxChannelInfo 13 }


    SpSpFunc OBJECT-TYPE
		SYNTAX DisplayString 
		MAX-ACCESS read-write
		STATUS current
		DESCRIPTION
			"3Bytes 格式a.b     a=0:关闭 a=1:打开   b=2/4/8 关闭时无意义    TSP=1.2(开启2倍扩频)"
	::= { RxChannelInfo 14 }

    SignalChannelStatus OBJECT-TYPE
		SYNTAX INTEGER 
		MAX-ACCESS read-only
		STATUS current
		DESCRIPTION
			"0: 失锁  1:锁定 "
	::= { RxChannelInfo 15 }

END
