MY-TX-CHANNEL-MIB DEFINITIONS ::= BEGIN 
IMPORTS 
	enterprises, OBJECT-TYPE, MODULE-IDENTITY
		FROM SNMPv2-SMI
	DisplayString, INTEGER
		FROM SNMPv2-TC;
		
	TxChannelInfo MODULE-IDENTITY ::= { enterprises 1000}
	
	
	TxIfFreq OBJECT-TYPE
		SYNTAX DisplayString 
		MAX-ACCESS read-only
		STATUS current
		DESCRIPTION
			"分辨率:100HZ  TFQ=1234.5678(发射频率1234.5678 MHZ)"
	::= { TxChannelInfo 1 }

    TxRfFreq OBJECT-TYPE
		SYNTAX DisplayString 
		MAX-ACCESS read-write
		STATUS current
		DESCRIPTION
			"终端发射频率 分辨率:100HZ 值= BUC LO ± TFQ, 如果BUC LO为零,则返回0  TTF=41251.3456(MHZ)"
	::= { TxChannelInfo 2 }

    TxModulateMode OBJECT-TYPE
		SYNTAX INTEGER 
		MAX-ACCESS read-write
		STATUS current
		DESCRIPTION
			"0:BPSK     1:QPSK     2:OQPSK      3:8PSK      4:16-QAM    5:8-QAM     6:16APSK    7:32APSK   TMD=1(QPSK方式)"
	::= { TxChannelInfo 3 }

    TxFecCodeRate OBJECT-TYPE
		SYNTAX INTEGER 
		MAX-ACCESS read-write
		STATUS current
		DESCRIPTION
			"0: 5/16(turbo)     1:21/44(turbo)      2:1/2       3:2/3(仅8-PSK TCM 或 8-QAM)     4:3/4       5:7/8   6:0.95(仅turbo)
            7:1/1(无FEC编码)    8:1/3       9:4/5       10:5/6      11:6/7      12:8/9      TCR=5(码率7/8)"
	::= { TxChannelInfo 4 }

    TxFecType OBJECT-TYPE
		SYNTAX INTEGER 
		MAX-ACCESS read-write
		STATUS current
		DESCRIPTION
			"6: Turbo  7:LDPC   (仅支持6和7)    RFT=6(Turbo编码)"
	::= { TxChannelInfo 5 }

    TxRolloffFactor OBJECT-TYPE
		SYNTAX INTEGER 
		MAX-ACCESS read-write
		STATUS current
		DESCRIPTION
			"0: 0.1     1:0.25      2:0.35      3:0.15      4:0.2"
	::= { TxChannelInfo 6 }

    TxBW OBJECT-TYPE
		SYNTAX DisplayString 
		MAX-ACCESS read-write
		STATUS current
		DESCRIPTION
			"单位KHZ 分辨率=100HZ   TBW=1500.0(发射带宽1.5MHZ)"
	::= { TxChannelInfo 7 }

    TxPower OBJECT-TYPE
		SYNTAX DisplayString 
		MAX-ACCESS read-write
		STATUS current
		DESCRIPTION
			"0 ~ -40 dBm(取负值)      TPL=13.4(发射功率-13.4dBm)"
	::= { TxChannelInfo 8 }

    TxSpectrumInvert OBJECT-TYPE
		SYNTAX INTEGER 
		MAX-ACCESS read-write
		STATUS current
		DESCRIPTION
			"0: 正常  1:翻转    TSI=0(发射频谱正常)"
	::= { TxChannelInfo 9 }

    TxSysmbolRate OBJECT-TYPE
		SYNTAX DisplayString 
		MAX-ACCESS read-only
		STATUS current
		DESCRIPTION
			"单位 ksymbols/sec 分辨率 1sps 范围：4.8ksps~15.0Msps   TSR=05123.456(发射符号速率5123.456ksymbols/sec)"
	::= { TxChannelInfo 10 }

    TxCarrierStatus OBJECT-TYPE
		SYNTAX INTEGER 
		MAX-ACCESS read-write
		STATUS current
		DESCRIPTION
			"0: 关闭  1:打开 2：RTI(收发抑制)   TXO=1(发射载波开关打开)"
	::= { TxChannelInfo 11 }

    TxDataRate OBJECT-TYPE
		SYNTAX DisplayString 
		MAX-ACCESS read-only
		STATUS current
		DESCRIPTION
			"发送数据速率 单位kbps 分辨率 1bps 范围：2.4kbps~30Mbps     TDR=01052.123(发送数据速率1052.123kbps)"
	::= { TxChannelInfo 12 }

    TxSpSpFunc OBJECT-TYPE
		SYNTAX DisplayString 
		MAX-ACCESS read-write
		STATUS current
		DESCRIPTION
			"3Bytes 格式a.b     a=0:关闭 a=1:打开   b=2/4/8 关闭时无意义    TSP=1.2"
	::= { TxChannelInfo 13 }
END
